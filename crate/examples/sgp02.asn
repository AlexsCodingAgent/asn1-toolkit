-- SGP.02 v4.2 — M2M (SMS/OTA) eUICC subset.
--
-- Hand-written subset covering how a classic M2M eUICC identifies itself and
-- how the Subscription Manager addresses a profile over OTA. This is the
-- pre-RSP generation: profiles move by SMS or IP push to the SM-SR, not by the
-- end user scanning a QR code.
--
-- Provenance: SGP.02 v4.2, "Remote Provisioning Architecture for Embedded UICC
-- Technical Specification". Curated subset, not an extract — GSMA
-- specifications are not redistributable.

M2mDefs DEFINITIONS AUTOMATIC TAGS EXTENSIBILITY IMPLIED ::=
BEGIN

-- ── Identifiers ──────────────────────────────────────────────────────────

-- ICCID as coded in EFiccid; APPLICATION 26 -> tag 5A
Iccid ::= [APPLICATION 26] OCTET STRING (SIZE(10))

-- Integrated Circuit Card Identifier, BCD-coded, as transmitted in OTA.
IccidBcd ::= OCTET STRING (SIZE(10))

-- M2M eUICC identity, per SGP.02 §3.1.3. Not given a top-level APPLICATION 26
-- tag: Iccid already carries that tag, and two types sharing it would leave the
-- decoder unable to name either. SGP.02 identifies the EID by context instead.
Eid ::= Octet16

-- ── OTA / SM-SR addressing ───────────────────────────────────────────────

-- The SM-SR reaches an eUICC by these parameters. SGP.02 §5.1.
SmSrAddress ::= SEQUENCE {
    smsrId           INTEGER (0..65535),
    smsrOid          OBJECT IDENTIFIER OPTIONAL,
    transport        Transport
}

Transport ::= CHOICE {
    sms     SmsAddress,
    http    HttpAddress,
    https   HttpAddress
}

SmsAddress ::= SEQUENCE {
    msisdn  OCTET STRING (SIZE(1..10)),
    tpad    OCTET STRING (SIZE(5)) OPTIONAL
}

HttpAddress ::= SEQUENCE {
    url     UTF8String (SIZE(1..255)),
    port    INTEGER (1..65535) OPTIONAL
}

-- ── Profile state on the eUICC ───────────────────────────────────────────

-- SGP.02 §3.1.1. Exactly one profile is enabled; the fallback profile (the
-- bootstrap) is outside the SEQUENCE OF and cannot be enabled by the SM-SR.
ProfileState ::= ENUMERATED {
    disabled(0),
    enabled(1),
    deleted(2)
}

EuiccConfiguration ::= SEQUENCE {
    eid              Eid,
    msisdn           OCTET STRING (SIZE(1..10)) OPTIONAL,
    fallbackProfile  IccidBcd OPTIONAL,
    profiles         SEQUENCE OF ProfileEntry
}

ProfileEntry ::= SEQUENCE {
    iccid   IccidBcd,
    state   ProfileState,
    isdPAid Aid
}

-- Application identifier, as in 3GPP TS 101 220.
Aid ::= OCTET STRING (SIZE(5..16))

-- ── OTA command envelope ─────────────────────────────────────────────────

-- Every SGP.02 OTA payload is wrapped in this. The counter is what prevents a
-- replayed command from being accepted twice.
OtaCommand ::= SEQUENCE {
    commandId    INTEGER (0..255),
    counter      INTEGER (0..4294967295),
    payload      OCTET STRING OPTIONAL
}

END
