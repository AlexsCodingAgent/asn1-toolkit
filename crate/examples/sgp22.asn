RSPDefinitions DEFINITIONS AUTOMATIC TAGS EXTENSIBILITY IMPLIED ::=
BEGIN

-- A valid subset of SGP.22 v3.1 Annex H (Remote SIM Provisioning).
-- SGP.22 splits this module across 98 blocks in the PDF; this is the
-- part that matters for profile metadata.

Octet8  ::= OCTET STRING (SIZE(8))
Octet16 ::= OCTET STRING (SIZE(16))
OctetTo16 ::= OCTET STRING (SIZE(1..16))
Octet32 ::= OCTET STRING (SIZE(32))

VersionType ::= OCTET STRING (SIZE(3))

-- ICCID as coded in EFiccid; corresponding tag is '5A'
Iccid ::= [APPLICATION 26] OCTET STRING (SIZE(10))

TransactionId ::= OCTET STRING (SIZE(1..16))

-- SGP.22 5.7.2. mccMnc is an OCTET STRING of 3, coded as 3GPP TS 24.008.
-- The ASN.1 says nothing about the internal layout: that is the
-- 3GPP spec's business, which is why a schema compiler alone will
-- not decode it for you.
OperatorId ::= SEQUENCE {
   mccMnc OCTET STRING (SIZE(3)),
   gid1   OCTET STRING OPTIONAL,
   gid2   OCTET STRING OPTIONAL
}

-- Profile metadata: the ProfileOwner carries mccMnc, which must match
-- the MCC/MNC in EF-IMSI (SGP.22 5.7.2).
StoreMetadataRequest ::= SEQUENCE {
   iccid           Iccid,
   serviceProviderName UTF8String (SIZE(1..32)),
   iccids          SEQUENCE OF Iccid,
   profileOwner    OperatorId OPTIONAL,
   profileName     UTF8String (SIZE(1..64)) OPTIONAL
}

-- ES9+ authenticateServer, abbreviated
AuthenticateServerRequest ::= SEQUENCE {
   serverSigned1   OCTET STRING,
   serverSignature1 OCTET STRING,
   euiccCiPKIdToBeUsed SubjectKeyIdentifier,
   serverCertificate OCTET STRING,
   ctxParams1      OCTET STRING
}

SubjectKeyIdentifier ::= OCTET STRING
END
