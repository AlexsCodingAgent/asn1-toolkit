SGP02Test DEFINITIONS AUTOMATIC TAGS ::=
BEGIN

-- Extracted from SGP.02-v4.2.txt by scripts/extract_spec_asn1.py.
-- Only type assignments that could be read with certainty are kept.
-- Prose, IMPORTS and value assignments are omitted; the count below is
-- therefore a floor on this spec's ASN.1 surface, not a total.

ResultCode ::= [0] INTEGER{ errorProfileRef (8), errorAlreadyEnabled (9), errorAlreadyDisabled (10), errorForbidden (12), undefinedError (127) }

UICCCapability ::= BIT STRING { /* Sequence is derived from ServicesList[] defined in SIMalliance PEDefinitions*/ contactlessSupport(0), usimSupport(1), isimSupport(2), csimSupport(3), akaMilenage(4), akaCave(5), akaTuak128(6), akaTuak256(7), gbaAuthenUsim(10), gbaAuthenISim(11), mbmsAuthenUsim(12), eapClient(13), multipleUsimSupport(16), same Profile multipleIsimSupport(17), same Profile multipleCsimSupport(18), berTlvFileSupport(19), dfLinkSupport(20), catTp(21), getIdentity(22), ETSI TS 102 221 [6] 33.501 [67] 33.501 [67] suciCalculatorApi(25) }

TreProperties ::= BIT STRING { isDiscrete(0), isIntegrated(1), usesRemoteMemory(2) the Remote Memory Protection Function described in SGP.01 [1] }

END
