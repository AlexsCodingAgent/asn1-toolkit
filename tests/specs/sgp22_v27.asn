SGP22v27Test DEFINITIONS AUTOMATIC TAGS ::=
BEGIN

-- Extracted from SGP.22-v2.7.txt by scripts/extract_spec_asn1.py.
-- Only type assignments that could be read with certainty are kept.
-- Prose, IMPORTS and value assignments are omitted; the count below is
-- therefore a floor on this spec's ASN.1 surface, not a total.

Octet1 ::= OCTET STRING(SIZE(1))

Octet4 ::= OCTET STRING (SIZE(4))

Octet8 ::= OCTET STRING (SIZE(8))

Octet16 ::= OCTET STRING (SIZE(16))

OctetTo16 ::= OCTET STRING (SIZE(1..16))

Octet32 ::= OCTET STRING (SIZE(32))

VersionType ::= OCTET STRING(SIZE(3))

Iccid ::= [APPLICATION 26] OCTET STRING (SIZE(10))

RemoteOpId ::= [2] INTEGER {installBoundProfilePackage(1)}

TransactionId ::= OCTET STRING (SIZE(1..16))

PprIds ::= BIT STRING { pprUpdateControl(0) }

OperatorId ::= SEQUENCE { mccMnc OCTET STRING (SIZE(3)), gid1 OCTET STRING OPTIONAL, gid2 OCTET STRING OPTIONAL }

BoundProfilePackage ::= [54] SEQUENCE { initialiseSecureChannelRequest [35] InitialiseSecureChannelRequest, firstSequenceOf87 [0] SEQUENCE OF [7] OCTET STRING, sequenceOf88 [1] SEQUENCE OF [8] OCTET STRING, secondSequenceOf87 [2] SEQUENCE OF [7] OCTET STRING OPTIONAL, sequenceOf86 [3] SEQUENCE OF [6] OCTET STRING }

ProfileInstallationResult ::= [55] SEQUENCE { profileInstallationResultData [39] ProfileInstallationResultData, euiccSignPIR EuiccSignPIR }

ProfileInstallationResultData ::= [39] SEQUENCE { transactionId[0] TransactionId, notificationMetadata[47] NotificationMetadata, smdpOid OBJECT IDENTIFIER, finalResult [2] CHOICE { successResult SuccessResult, errorResult ErrorResult } }

EuiccSignPIR ::= [APPLICATION 55] OCTET STRING

SuccessResult ::= SEQUENCE { aid [APPLICATION 15] OCTET STRING (SIZE (5..16)), simaResponse OCTET STRING [5] }

ErrorResult ::= SEQUENCE { bppCommandId BppCommandId, errorReason ErrorReason, simaResponse OCTET STRING OPTIONAL }

BppCommandId ::= INTEGER {initialiseSecureChannel(0), configureISDP(1), storeMetadata(2), storeMetadata2(3), replaceSessionKeys(4), loadProfileElements(5)}

ErrorReason ::= INTEGER { incorrectInputValues(1), invalidSignature(2), invalidTransactionId(3), unsupportedCrtValues(4), unsupportedRemoteOperationType(5), unsupportedProfileClass(6), scp03tStructureError(7), scp03tSecurityError(8), installFailedDueToIccidAlreadyExistsOnEuicc(9), installFailedDueToInsufficientMemoryForProfile(10), installFailedDueToInterruption(11), installFailedDueToPEProcessingError(12), installFailedDueToDataMismatch(13), testProfileInstallFailedDueToInvalidNaaKey(14), pprNotAllowed(15), installFailedDueToInsufficientMinimumSecurityLevel(31), installFailedDueToServerAddressAbsentInEuiccAllowList(32), installFailedDueToUnknownError(127) }

DeviceInfo ::= SEQUENCE { tac Octet4, deviceCapabilities DeviceCapabilities, imei Octet8 OPTIONAL }

DeviceCapabilities ::= SEQUENCE { definition gsmSupportedRelease VersionType OPTIONAL, utranSupportedRelease VersionType OPTIONAL, cdma2000onexSupportedRelease VersionType OPTIONAL, cdma2000hrpdSupportedRelease VersionType OPTIONAL, cdma2000ehrpdSupportedRelease VersionType OPTIONAL, eutranEpcSupportedRelease VersionType OPTIONAL, contactlessSupportedRelease VersionType OPTIONAL, rspCrlSupportedVersion VersionType OPTIONAL, nrEpcSupportedRelease VersionType OPTIONAL, nr5gcSupportedRelease VersionType OPTIONAL, eutran5gcSupportedRelease VersionType OPTIONAL, lpaSvn VersionType OPTIONAL, catSupportedClasses CatSupportedClasses OPTIONAL, of SGP.22 euiccFormFactorType EuiccFormFactorType OPTIONAL, of SGP.22 deviceAdditionalFeatureSupport DeviceAdditionalFeatureSupport OPTIONAL }

DeviceAdditionalFeatureSupport ::= SEQUENCE { naiSupport VersionType OPTIONAL, groupOfDeviceManufacturerOid OBJECT IDENTIFIER OPTIONAL Manufacturer or the Group of Device Manufacturers as defined in SGP.29 }

CatSupportedClasses ::= BIT STRING

EuiccFormFactorType ::= INTEGER

SegmentedCrlList ::= SEQUENCE OF CertificateList

ExpirationDate ::= Time

TotalPartialCrlNumber ::= INTEGER

PartialCrlNumber ::= INTEGER

ActivationCodeRetrievalInfo ::= CHOICE { activationCodeForProfileRedownload [1] UTF8String (SIZE(0..255)), Code to be used for Profile re-download activationCodeRetrievalAvailable [2] BOOLEAN, retryDelay [3] INTEGER }

UpdateMetadataRequest ::= [42] SEQUENCE { serviceProviderName [17] UTF8String (SIZE(0..32)) OPTIONAL, profileName [18] UTF8String (SIZE(0..64)) OPTIONAL, iconType [19] IconType OPTIONAL, icon [20] OCTET STRING (SIZE(0..1024)) OPTIONAL, profilePolicyRules [25] PprIds OPTIONAL, serviceSpecificDataStoredInEuicc [34] VendorSpecificExtension OPTIONAL, reserved103 [103] BOOLEAN OPTIONAL }

InitialiseSecureChannelRequest ::= [35] SEQUENCE { remoteOpId RemoteOpId, transactionId [0] TransactionId, controlRefTemplate[6] IMPLICIT ControlRefTemplate, (Key Agreement). Current specification considers a subset of CRT specified in GlobalPlatform Card Specification [8] section 6.4.2.3 for the Mutual Authentication Data Field smdpOtpk [APPLICATION 73] OCTET STRING, GlobalPlatform Card Specification [8] section 6.4.2.3 for ePK.OCE.ECKA, tag '5F49' smdpSign [APPLICATION 55] OCTET STRING }

ControlRefTemplate ::= SEQUENCE { keyType[0] Octet1, [8] Table 11-16, AES= '88', Tag '80' keyLen[1] Octet1, length SHALL by 0x10 bytes, Tag '81' hostId[4] OctetTo16 }

ConfigureISDPRequest ::= [36] SEQUENCE { dpProprietaryData [24] DpProprietaryData OPTIONAL }

DpProprietaryData ::= SEQUENCE { 128 bytes dpOid OBJECT IDENTIFIER }

NotificationEvent ::= BIT STRING { notificationInstall(0), notificationEnable(1), notificationDisable(2), notificationDelete(3) }

NotificationConfigurationInformation ::= SEQUENCE { profileManagementOperation NotificationEvent, notificationAddress UTF8String }

OPENTYPE ::= CLASS { &typeId OBJECT IDENTIFIER, &Type }

VendorSpecificExtension ::= SEQUENCE OF SEQUENCE { vendorOid [0] OPENTYPE.&typeId, extension vendorSpecificData [1] OPENTYPE.&Type }

ReplaceSessionKeysRequest ::= [38] SEQUENCE { /*The new initial MAC chaining value*/ initialMacChainingValue OCTET STRING, /*New session key value for encryption/decryption (PPK-ENC)*/ ppkEnc OCTET STRING, /*New session key value of the session key C-MAC computation/verification (PPK- MAC)*/ ppkCmac OCTET STRING }

ISDRProprietaryApplicationTemplate ::= [PRIVATE 0] SEQUENCE { svn [2] VersionType, lpaeSupport BIT STRING { lpaeUsingCat(0), lpaeUsingScws(1) } OPTIONAL }

LpaeActivationRequest ::= [66] SEQUENCE { lpaeOption BIT STRING { activateCatBasedLpae(0), activateScwsBasedLpae(1) } }

LpaeActivationResponse ::= [66] SEQUENCE { lpaeActivationResult INTEGER {ok(0), notSupported(1)} }

EuiccConfiguredAddressesRequest ::= [60] SEQUENCE {}

EuiccConfiguredAddressesResponse ::= [60] SEQUENCE { defaultDpAddress UTF8String OPTIONAL, rootDsAddress UTF8String }

SetDefaultDpAddressRequest ::= [63] SEQUENCE { defaultDpAddress UTF8String }

SetDefaultDpAddressResponse ::= [63] SEQUENCE { setDefaultDpAddressResult INTEGER { ok (0), undefinedError (127)} }

PrepareDownloadRequest ::= [33] SEQUENCE { smdpSigned2 SmdpSigned2, smdpSignature2 [APPLICATION 55] OCTET STRING, hashCc Octet32 OPTIONAL, smdpCertificate Certificate }

SmdpSigned2 ::= SEQUENCE { transactionId [0] TransactionId, SM-DP+ ccRequiredFlag BOOLEAN, bppEuiccOtpk [APPLICATION 73] OCTET STRING OPTIONAL }

PrepareDownloadResponse ::= [33] CHOICE { downloadResponseOk PrepareDownloadResponseOk, downloadResponseError PrepareDownloadResponseError }

PrepareDownloadResponseOk ::= SEQUENCE { euiccSigned2 EUICCSigned2, euiccSignature2 [APPLICATION 55] OCTET STRING }

EUICCSigned2 ::= SEQUENCE { transactionId [0] TransactionId, euiccOtpk [APPLICATION 73] OCTET STRING, hashCc Octet32 OPTIONAL }

PrepareDownloadResponseError ::= SEQUENCE { transactionId [0] TransactionId, downloadErrorCode DownloadErrorCode }

DownloadErrorCode ::= INTEGER {invalidCertificate(1), invalidSignature(2), unsupportedCurve(3), noSessionContext(4), invalidTransactionId(5), undefinedError(127)}

GetEuiccChallengeRequest ::= [46] SEQUENCE {}

GetEuiccChallengeResponse ::= [46] SEQUENCE { euiccChallenge Octet16 }

GetEuiccInfo1Request ::= [32] SEQUENCE {}

GetEuiccInfo2Request ::= [34] SEQUENCE {}

EUICCInfo1 ::= [32] SEQUENCE { svn [2] VersionType, euiccCiPKIdListForVerification [9] SEQUENCE OF SubjectKeyIdentifier, CI Public Key Identifiers supported on the eUICC for signature verification euiccCiPKIdListForSigning [10] SEQUENCE OF SubjectKeyIdentifier Public Key Identifier supported on the eUICC for signature creation }

EUICCInfo2 ::= [34] SEQUENCE { profileVersion [1] VersionType, supported svn [2] VersionType, euiccFirmwareVer [3] VersionType, extCardResource [4] OCTET STRING, uiccCapability [5] UICCCapability, ts102241Version [6] VersionType OPTIONAL, globalplatformVersion [7] VersionType OPTIONAL, rspCapability [8] RspCapability, euiccCiPKIdListForVerification [9] SEQUENCE OF SubjectKeyIdentifier, CI Public Key Identifiers supported on the eUICC for signature verification euiccCiPKIdListForSigning [10] SEQUENCE OF SubjectKeyIdentifier, Public Key Identifier supported on the eUICC for signature creation euiccCategory [11] INTEGER { basicEuicc(1), mediumEuicc(2), contactlessEuicc(3) } OPTIONAL, forbiddenProfilePolicyRules [25] PprIds OPTIONAL, ppVersion VersionType, sasAcreditationNumber UTF8String (SIZE(0..64)), certificationDataObject [12] CertificationDataObject OPTIONAL, treProperties [13] BIT STRING { isDiscrete(0), isIntegrated(1), usesRemoteMemory(2) Remote Memory Protection Function described in SGP.21 [4] } OPTIONAL, treProductReference [14] UTF8String OPTIONAL, GlobalPlatform DLOA specification [57] additionalEuiccProfilePackageVersions [15] SEQUENCE OF VersionType OPTIONAL, lpaMode [16] LpaMode OPTIONAL, euiccCiPKIdListForSigningV3 [17] SEQUENCE OF SubjectKeyIdentifier OPTIONAL, additionalEuiccInfo [18] OCTET STRING (SIZE(0..32)) OPTIONAL, highestSvn [19] VersionType OPTIONAL, iotSpecificInfo [20] IoTSpecificInfo OPTIONAL, euiccMinimumSecurityLevel [21] OCTET STRING (SIZE (1)) OPTIONAL –- value for eUICC Minimum Security Level Check }

RspCapability ::= BIT STRING { additionalProfile(0), crlSupport(1), rpmSupport(2), testProfileSupport (3), deviceInfoExtensibilitySupport (4), Device Info serviceSpecificDataSupport (5), Profile Metadata osUpdateSupport (19), iotSpecificMetadataSupport (26), iotSpecificProfileInfo defined in SGP.32 [97] mslCheckSupport (27), rspServerTestProfileAllowlistCheckSupport (28) – support for RSP Server Test Profile Allow-list Check}

CertificationDataObject ::= SEQUENCE { platformLabel UTF8String, DLOA specification [57] discoveryBaseURL UTF8String Registrar as defined in GlobalPlatform DLOA specification [57] }

LpaMode ::= INTEGER

IoTSpecificInfo ::= SEQUENCE {}

ListNotificationRequest ::= [40] SEQUENCE { profileManagementOperation [1] NotificationEvent OPTIONAL }

ListNotificationResponse ::= [40] CHOICE { notificationMetadataList SEQUENCE OF NotificationMetadata, listNotificationsResultError INTEGER {undefinedError(127)} }

NotificationMetadata ::= [47] SEQUENCE { seqNumber [0] INTEGER, profileManagementOperation [1] NotificationEvent, /*Only one bit SHALL be set to 1*/ notificationAddress UTF8String, iccid Iccid OPTIONAL }

RetrieveNotificationsListRequest ::= [43] SEQUENCE { searchCriteria CHOICE { seqNumber [0] INTEGER, profileManagementOperation [1] NotificationEvent } OPTIONAL }

RetrieveNotificationsListResponse ::= [43] CHOICE { notificationList SEQUENCE OF PendingNotification, notificationsListResultError INTEGER { undefinedError(127)} }

PendingNotification ::= CHOICE { profileInstallationResult [55] ProfileInstallationResult, otherSignedNotification OtherSignedNotification }

OtherSignedNotification ::= SEQUENCE { tbsOtherNotification NotificationMetadata, euiccNotificationSignature [APPLICATION 55] OCTET STRING, tbsOtherNotification, Tag '5F37' euiccCertificate Certificate, the EUM eumCertificate Certificate requested CI }

NotificationSentRequest ::= [48] SEQUENCE { seqNumber [0] INTEGER }

NotificationSentResponse ::= [48] SEQUENCE { deleteNotificationStatus INTEGER {ok(0), nothingToDelete(1), undefinedError(127)} }

LoadCRLRequest ::= [53] SEQUENCE { crl CertificateList }

LoadCRLResponse ::= [53] CHOICE { loadCRLResponseOk LoadCRLResponseOk, loadCRLResponseError LoadCRLResponseError }

LoadCRLResponseOk ::= SEQUENCE { missingParts SEQUENCE OF INTEGER OPTIONAL }

LoadCRLResponseError ::= INTEGER {invalidSignature(1), invalidCRLFormat(2), notEnoughMemorySpace(3), verificationKeyNotFound(4), fresherCrlAlreadyLoaded(5), baseCrlMissing(6), undefinedError(127)}

AuthenticateServerRequest ::= [56] SEQUENCE { serverSigned1 ServerSigned1, serverSignature1 [APPLICATION 55] OCTET STRING, euiccCiPKIdToBeUsed SubjectKeyIdentifier, serverCertificate Certificate, ctxParams1 CtxParams1 }

ServerSigned1 ::= SEQUENCE { transactionId [0] TransactionId, Server euiccChallenge [1] Octet16, serverAddress [3] UTF8String, serverChallenge [4] Octet16 }

CtxParams1 ::= CHOICE { ctxParamsForCommonAuthentication CtxParamsForCommonAuthentication }

CtxParamsForCommonAuthentication ::= SEQUENCE { matchingId UTF8String OPTIONAL, deviceInfo DeviceInfo }

AuthenticateServerResponse ::= [56] CHOICE { authenticateResponseOk AuthenticateResponseOk, authenticateResponseError AuthenticateResponseError }

AuthenticateResponseOk ::= SEQUENCE { euiccSigned1 EuiccSigned1, euiccSignature1 [APPLICATION 55] OCTET STRING, euiccCertificate Certificate, the EUM eumCertificate Certificate requested CI }

EuiccSigned1 ::= SEQUENCE { transactionId [0] TransactionId, serverAddress [3] UTF8String, serverChallenge [4] Octet16, euiccInfo2 [34] EUICCInfo2, ctxParams1 CtxParams1 }

AuthenticateResponseError ::= SEQUENCE { transactionId [0] TransactionId, authenticateErrorCode AuthenticateErrorCode }

AuthenticateErrorCode ::= INTEGER {invalidCertificate(1), invalidSignature(2), unsupportedCurve(3), noSessionContext(4), invalidOid(5), euiccChallengeMismatch(6), ciPKUnknown(7), undefinedError(127)}

CancelSessionRequest ::= [65] SEQUENCE { transactionId TransactionId, reason CancelSessionReason }

CancelSessionReason ::= INTEGER {endUserRejection(0), postponed(1), timeout(2), pprNotAllowed(3), metadataMismatch(4), loadBppExecutionError(5), undefinedReason(127)}

CancelSessionResponse ::= [65] CHOICE { cancelSessionResponseOk CancelSessionResponseOk, cancelSessionResponseError INTEGER {invalidTransactionId(5), undefinedError(127)} }

CancelSessionResponseOk ::= SEQUENCE { euiccCancelSessionSigned EuiccCancelSessionSigned, euiccCancelSessionSignature [APPLICATION 55] OCTET STRING }

EuiccCancelSessionSigned ::= SEQUENCE { transactionId TransactionId, smdpOid OBJECT IDENTIFIER, reason CancelSessionReason }

ProfileInfoListRequest ::= [45] SEQUENCE { searchCriteria [0] CHOICE { isdpAid [APPLICATION 15] OctetTo16, iccid Iccid, profileClass [21] ProfileClass } OPTIONAL, tagList [APPLICATION 28] OCTET STRING OPTIONAL, iotSpecificTagList [APPLICATION 29] OCTET STRING OPTIONAL }

ProfileInfoListResponse ::= [45] CHOICE { profileInfoListOk SEQUENCE OF ProfileInfo, profileInfoListError ProfileInfoListError }

ProfileInfo ::= [PRIVATE 3] SEQUENCE { iccid Iccid OPTIONAL, isdpAid [APPLICATION 15] OctetTo16 OPTIONAL, Profile, tag '4F' profileState [112] ProfileState OPTIONAL, profileNickname [16] UTF8String (SIZE(0..64)) OPTIONAL, serviceProviderName [17] UTF8String (SIZE(0..32)) OPTIONAL, profileName [18] UTF8String (SIZE(0..64)) OPTIONAL, iconType [19] IconType OPTIONAL, icon [20] OCTET STRING (SIZE(0..1024)) OPTIONAL, ES10c:GetProfilesInfo profileClass [21] ProfileClass OPTIONAL, notificationConfigurationInfo [22] SEQUENCE OF NotificationConfigurationInformation OPTIONAL, profileOwner [23] OperatorId OPTIONAL, dpProprietaryData [24] DpProprietaryData OPTIONAL, profilePolicyRules [25] PprIds OPTIONAL, serviceSpecificDataStoredInEuicc [34] VendorSpecificExtension OPTIONAL, ecallIndication [123] BOOLEAN OPTIONAL, fallbackAttribute [38] BOOLEAN DEFAULT FALSE, [97] fallbackAllowed [103] BOOLEAN OPTIONAL, iotSpecificProfileInfo [100] SEQUENCE {} OPTIONAL }

IconType ::= INTEGER {jpg(0), png(1)}

ProfileState ::= INTEGER {disabled(0), enabled(1)}

ProfileClass ::= INTEGER {test(0), provisioning(1), operational(2)}

ProfileInfoListError ::= INTEGER {incorrectInputValues(1), undefinedError(127)}

EnableProfileRequest ::= [49] SEQUENCE { profileIdentifier CHOICE { isdpAid [APPLICATION 15] OctetTo16, iccid Iccid }, refreshFlag BOOLEAN }

EnableProfileResponse ::= [49] SEQUENCE { enableResult INTEGER {ok(0), iccidOrAidNotFound (1), profileNotInDisabledState(2), disallowedByPolicy(3), wrongProfileReenabling(4), catBusy(5), undefinedError(127)} }

DisableProfileRequest ::= [50] SEQUENCE { profileIdentifier CHOICE { isdpAid [APPLICATION 15] OctetTo16, iccid Iccid }, refreshFlag BOOLEAN }

DisableProfileResponse ::= [50] SEQUENCE { disableResult INTEGER {ok(0), iccidOrAidNotFound (1), profileNotInEnabledState(2), disallowedByPolicy(3), catBusy(5), undefinedError(127)} }

DeleteProfileRequest ::= [51] CHOICE { isdpAid [APPLICATION 15] OctetTo16, iccid Iccid }

DeleteProfileResponse ::= [51] SEQUENCE { deleteResult INTEGER {ok(0), iccidOrAidNotFound (1), profileNotInDisabledState(2), disallowedByPolicy(3), undefinedError(127)} }

EuiccMemoryResetRequest ::= [52] SEQUENCE { resetOptions [2] BIT STRING { deleteOperationalProfiles(0), deleteFieldLoadedTestProfiles(1), resetDefaultSmdpAddress(2)} }

EuiccMemoryResetResponse ::= [52] SEQUENCE { resetResult INTEGER {ok(0), nothingToDelete(1), catBusy(5), undefinedError(127)} }

GetEuiccDataRequest ::= [62] SEQUENCE { tagList [APPLICATION 28] Octet1 }

GetEuiccDataResponse ::= [62] SEQUENCE { eidValue [APPLICATION 26] Octet16 }

SetNicknameRequest ::= [41] SEQUENCE { iccid Iccid, profileNickname [16] UTF8String (SIZE(0..64)) }

SetNicknameResponse ::= [41] SEQUENCE { setNicknameResult INTEGER {ok(0), iccidNotFound (1), undefinedError(127)} }

GetRatRequest ::= [67] SEQUENCE {}

GetRatResponse ::= [67] SEQUENCE { rat RulesAuthorisationTable }

RulesAuthorisationTable ::= SEQUENCE OF ProfilePolicyAuthorisationRule

ProfilePolicyAuthorisationRule ::= SEQUENCE { pprIds PprIds, allowedOperators SEQUENCE OF OperatorId, pprFlags BIT STRING {consentRequired(0)} }

RemoteProfileProvisioningRequest ::= [2] CHOICE { initiateAuthenticationRequest [57] InitiateAuthenticationRequest, authenticateClientRequest [59] AuthenticateClientRequest, getBoundProfilePackageRequest [58] GetBoundProfilePackageRequest, cancelSessionRequestEs9 [65] CancelSessionRequestEs9, handleNotification [61] HandleNotification }

RemoteProfileProvisioningResponse ::= [2] CHOICE { initiateAuthenticationResponse [57] InitiateAuthenticationResponse, authenticateClientResponseEs9 [59] AuthenticateClientResponseEs9, getBoundProfilePackageResponse [58] GetBoundProfilePackageResponse, cancelSessionResponseEs9 [65] CancelSessionResponseEs9, authenticateClientResponseEs11 [64] AuthenticateClientResponseEs11 }

InitiateAuthenticationRequest ::= [57] SEQUENCE { euiccChallenge [1] Octet16, smdpAddress [3] UTF8String, euiccInfo1 EUICCInfo1 }

InitiateAuthenticationResponse ::= [57] CHOICE { initiateAuthenticationOk InitiateAuthenticationOkEs9, initiateAuthenticationError INTEGER { invalidDpAddress(1), euiccVersionNotSupportedByDp(2), ciPKIdNotSupported(3) } }

InitiateAuthenticationOkEs9 ::= SEQUENCE { transactionId [0]TransactionId, serverSigned1 ServerSigned1, serverSignature1 [APPLICATION 55] OCTET STRING, euiccCiPKIdToBeUsed SubjectKeyIdentifier, serverCertificate Certificate }

AuthenticateClientRequest ::= [59] SEQUENCE { transactionId [0] TransactionId, authenticateServerResponse [56] AuthenticateServerResponse, useMatchingIdForAcr NULL OPTIONAL }

AuthenticateClientResponseEs9 ::= [59] CHOICE { authenticateClientOk [0] AuthenticateClientOk, authenticateClientError [1] INTEGER { eumCertificateInvalid(1), eumCertificateExpired(2), euiccCertificateInvalid(3), euiccCertificateExpired(4), euiccSignatureInvalid(5), matchingIdRefused(6), eidMismatch(7), noEligibleProfile(8), ciPKUnknown(9), invalidTransactionId(10), insufficientMemory(11), of SGP.22 downloadOrderExpired(18), undefinedError(127) }, authenticateClientOkAcr [5] AuthenticateClientOkAcr }

AuthenticateClientOk ::= SEQUENCE { transactionId [0] TransactionId, profileMetaData [37] StoreMetadataRequest, smdpSigned2 SmdpSigned2, smdpSignature2 [APPLICATION 55] OCTET STRING, smdpCertificate Certificate }

AuthenticateClientOkAcr ::= SEQUENCE { transactionId [0] TransactionId, profileMetaData [37] StoreMetadataRequest }

GetBoundProfilePackageRequest ::= [58] SEQUENCE { transactionId [0] TransactionId, prepareDownloadResponse [33] PrepareDownloadResponse }

GetBoundProfilePackageResponse ::= [58] CHOICE { getBoundProfilePackageOk GetBoundProfilePackageOk, getBoundProfilePackageError INTEGER { euiccSignatureInvalid(1), confirmationCodeMissing(2), confirmationCodeRefused(3), confirmationCodeRetriesExceeded(4), bppRebindingRefused(5), invalidTransactionId(95), undefinedError(127) } }

GetBoundProfilePackageOk ::= SEQUENCE { transactionId [0] TransactionId, boundProfilePackage [54] BoundProfilePackage }

HandleNotification ::= [61] SEQUENCE { pendingNotification PendingNotification }

CancelSessionRequestEs9 ::= [65] SEQUENCE { transactionId TransactionId, cancelSessionResponse CancelSessionResponse ES10b.CancelSession function }

CancelSessionResponseEs9 ::= [65] CHOICE { cancelSessionOk CancelSessionOk, cancelSessionError INTEGER { invalidTransactionId(1), euiccSignatureInvalid(2), undefinedError(127) } }

CancelSessionOk ::= SEQUENCE {}

AuthenticateClientResponseEs11 ::= [64] CHOICE { authenticateClientOk AuthenticateClientOkEs11, authenticateClientError INTEGER { eumCertificateInvalid(1), eumCertificateExpired(2), euiccCertificateInvalid(3), euiccCertificateExpired(4), euiccSignatureInvalid(5), eventIdUnknown(6), invalidTransactionId(7), undefinedError(127) } }

AuthenticateClientOkEs11 ::= SEQUENCE { transactionId TransactionId, eventEntries SEQUENCE OF EventEntries }

EventEntries ::= SEQUENCE { eventId UTF8String, rspServerAddress UTF8String }

END
